FME workspace ResultsPolyRoads2Line_FME2012.fmw

Parameters:
- SourceDataset_GEODATABASE_SDE = sde   # Source ESRI Geodatabase (ArcSDE) Dataset
- DestDataset_FILEGDB = T:\roadintegrator\results.gdb   # File Geodatabase|*.gdb Destination Geodatabase

Readers:
- GEODATABASE_SDE_1: GEODATABASE_SDE from $(SourceDataset_GEODATABASE_SDE)

Writers:
- FILEGDB_1: FILEGDB to $(DestDataset_FILEGDB)

WHSE_FOREST_VEGETATION.RSLT_FOREST_COVER_INV_SVW (reader GEODATABASE_SDE_1)
    attributes: geodb_oid integer, FOREST_COVER_ID integer, STOCKING_STANDARD_UNIT_ID integer, OPENING_ID integer, STANDARDS_UNIT_ID char(4), SILV_POLYGON_NUMBER char(30), SILV_POLYGON_AREA double, SILV_POLYGON_NET_AREA double, SILV_NON_MAPPED_AREA double, STOCKING_STATUS_CODE char(3), STOCKING_TYPE_CODE char(3), STOCKING_CLASS_CODE char(1), SILV_RESERVE_CODE char(1), SILV_RESERVE_OBJECTIVE_CODE char(3), TREE_COVER_PATTERN_CODE char(1), REENTRY_YEAR smallint, REFERENCE_YEAR smallint, SITE_INDEX integer, SITE_INDEX_SOURCE_CODE char(1), BGC_ZONE_CODE char(4), BGC_SUBZONE_CODE char(3), BGC_VARIANT char(1), BGC_PHASE char(1), BEC_SITE_SERIES char(4), BEC_SITE_TYPE char(3), BEC_SERAL char(4), FOREST_COVER_INV_TYPE char(7), I_FOREST_COVER_LAYER_ID integer, I_TOTAL_STEMS_PER_HA integer, I_TOTAL_WELL_SPACED_STEMS_HA integer,
      I_WELL_SPACED_STEMS_PER_HA integer, I_FREE_GROWING_STEMS_PER_HA integer, I_CROWN_CLOSURE_PERCENT smallint, I_BASAL_AREA integer, I_SPECIES_CODE_1 char(8), I_SPECIES_PERCENT_1 smallint, I_SPECIES_AGE_1 integer, I_SPECIES_HEIGHT_1 float, I_SPECIES_CODE_2 char(8), I_SPECIES_PERCENT_2 smallint, I_SPECIES_AGE_2 integer, I_SPECIES_HEIGHT_2 float, I_SPECIES_CODE_3 char(8), I_SPECIES_PERCENT_3 smallint, I_SPECIES_CODE_4 char(8), I_SPECIES_PERCENT_4 smallint, I_SPECIES_CODE_5 char(8), I_SPECIES_PERCENT_5 smallint, I_MORE_SPECIES_EXIST_IND char(1), I_INV_LABEL char(160), I1_FOREST_COVER_LAYER_ID integer, I1_TOTAL_STEMS_PER_HA integer, I1_TOTAL_WELL_SPACED_STEMS_HA integer, I1_WELL_SPACED_STEMS_PER_HA integer, I1_FREE_GROWING_STEMS_PER_HA integer, I1_CROWN_CLOSURE_PERCENT smallint, I1_BASAL_AREA integer, I1_SPECIES_CODE_1 char(8), I1_SPECIES_PERCENT_1 smallint, I1_SPECIES_AGE_1 integer,
      I1_SPECIES_HEIGHT_1 float, I1_SPECIES_CODE_2 char(8), I1_SPECIES_PERCENT_2 smallint, I1_SPECIES_AGE_2 integer, I1_SPECIES_HEIGHT_2 float, I1_SPECIES_CODE_3 char(8), I1_SPECIES_PERCENT_3 smallint, I1_SPECIES_CODE_4 char(8), I1_SPECIES_PERCENT_4 smallint, I1_SPECIES_CODE_5 char(8), I1_SPECIES_PERCENT_5 smallint, I1_MORE_SPECIES_EXIST_IND char(1), I1_INV_LABEL char(160), I2_FOREST_COVER_LAYER_ID integer, I2_TOTAL_STEMS_PER_HA integer, I2_TOTAL_WELL_SPACED_STEMS_HA integer, I2_WELL_SPACED_STEMS_PER_HA integer, I2_FREE_GROWING_STEMS_PER_HA integer, I2_CROWN_CLOSURE_PERCENT smallint, I2_BASAL_AREA integer, I2_SPECIES_CODE_1 char(8), I2_SPECIES_PERCENT_1 smallint, I2_SPECIES_AGE_1 integer, I2_SPECIES_HEIGHT_1 float, I2_SPECIES_CODE_2 char(8), I2_SPECIES_PERCENT_2 smallint, I2_SPECIES_AGE_2 integer, I2_SPECIES_HEIGHT_2 float, I2_SPECIES_CODE_3 char(8), I2_SPECIES_PERCENT_3 smallint,
      I2_SPECIES_CODE_4 char(8), I2_SPECIES_PERCENT_4 smallint, I2_SPECIES_CODE_5 char(8), I2_SPECIES_PERCENT_5 smallint, I2_MORE_SPECIES_EXIST_IND char(1), I2_INV_LABEL char(160), I3_FOREST_COVER_LAYER_ID integer, I3_TOTAL_STEMS_PER_HA integer, I3_TOTAL_WELL_SPACED_STEMS_HA integer, I3_WELL_SPACED_STEMS_PER_HA integer, I3_FREE_GROWING_STEMS_PER_HA integer, I3_CROWN_CLOSURE_PERCENT smallint, I3_BASAL_AREA integer, I3_SPECIES_CODE_1 char(8), I3_SPECIES_PERCENT_1 smallint, I3_SPECIES_AGE_1 integer, I3_SPECIES_HEIGHT_1 float, I3_SPECIES_CODE_2 char(8), I3_SPECIES_PERCENT_2 smallint, I3_SPECIES_AGE_2 integer, I3_SPECIES_HEIGHT_2 float, I3_SPECIES_CODE_3 char(8), I3_SPECIES_PERCENT_3 smallint, I3_SPECIES_CODE_4 char(8), I3_SPECIES_PERCENT_4 smallint, I3_SPECIES_CODE_5 char(8), I3_SPECIES_PERCENT_5 smallint, I3_MORE_SPECIES_EXIST_IND char(1), I3_INV_LABEL char(160), I4_FOREST_COVER_LAYER_ID integer,
      I4_TOTAL_STEMS_PER_HA integer, I4_TOTAL_WELL_SPACED_STEMS_HA integer, I4_WELL_SPACED_STEMS_PER_HA integer, I4_FREE_GROWING_STEMS_PER_HA integer, I4_CROWN_CLOSURE_PERCENT smallint, I4_BASAL_AREA integer, I4_SPECIES_CODE_1 char(8), I4_SPECIES_PERCENT_1 smallint, I4_SPECIES_AGE_1 integer, I4_SPECIES_HEIGHT_1 float, I4_SPECIES_CODE_2 char(8), I4_SPECIES_PERCENT_2 smallint, I4_SPECIES_AGE_2 integer, I4_SPECIES_HEIGHT_2 float, I4_SPECIES_CODE_3 char(8), I4_SPECIES_PERCENT_3 smallint, I4_SPECIES_CODE_4 char(8), I4_SPECIES_PERCENT_4 smallint, I4_SPECIES_CODE_5 char(8), I4_SPECIES_PERCENT_5 smallint, I4_MORE_SPECIES_EXIST_IND char(1), I4_INV_LABEL char(160), GEOMETRY_EXIST_IND char(1), FEATURE_AREA double, FEATURE_PERIMETER double, CAPTURE_METHOD_CODE char(30), DATA_SOURCE_CODE char(10), OBSERVATION_DATE date, DATA_QUALITY_COMMENT char(255), FOREST_COVER_WHO_CREATED char(30),
      FOREST_COVER_WHEN_CREATED date, FOREST_COVER_WHO_UPDATED char(30), FOREST_COVER_WHEN_UPDATED date, FEATURE_CLASS_SKEY integer, OBJECTID integer, GEOMETRY.AREA double, GEOMETRY.LEN double
    -> CenterLineReplacer
CenterLineReplacer
    MODE = Medial Axis
    CENTERLINE -> ResultsRoads (writer FILEGDB_1)
ResultsRoads (writer FILEGDB_1)
    attributes: I4_MORE_SPECIES_EXIST_IND text(20), I1_MORE_SPECIES_EXIST_IND text(20), FOREST_COVER_ID text(20), I2_SPECIES_PERCENT_1 text(20), I_SPECIES_HEIGHT_2 text(20), I_SPECIES_CODE_3 text(20), I_SPECIES_HEIGHT_1 text(20), SILV_RESERVE_OBJECTIVE_CODE text(20), I_CROWN_CLOSURE_PERCENT text(20), I_SPECIES_AGE_1 text(20), I2_BASAL_AREA text(20), I_SPECIES_AGE_2 text(20), I3_SPECIES_AGE_1 text(20), OBSERVATION_DATE text(20), geodb_oid text(20), REFERENCE_YEAR text(20), I2_SPECIES_CODE_4 text(20), I_SPECIES_CODE_4 text(20), I2_SPECIES_CODE_5 text(20), I2_SPECIES_HEIGHT_2 text(20), SITE_INDEX_SOURCE_CODE text(20), I2_SPECIES_HEIGHT_1 text(20), I2_SPECIES_CODE_1 text(20), I3_SPECIES_PERCENT_3 text(20), I2_SPECIES_CODE_2 text(20), I2_SPECIES_CODE_3 text(20), I_INV_LABEL text(20), GEOMETRY_EXIST_IND text(20), FOREST_COVER_WHO_UPDATED text(20), I1_SPECIES_PERCENT_5 text(20),
      I3_SPECIES_PERCENT_4 text(20), FOREST_COVER_INV_TYPE text(20), I1_INV_LABEL text(20), GEOMETRY_LEN text(20), I_FOREST_COVER_LAYER_ID text(20), SITE_INDEX text(20), I_SPECIES_CODE_1 text(20), CAPTURE_METHOD_CODE text(20), I_TOTAL_WELL_SPACED_STEMS_HA text(20), I_FREE_GROWING_STEMS_PER_HA text(20), I3_WELL_SPACED_STEMS_PER_HA text(20), I1_SPECIES_CODE_4 text(20), I1_FREE_GROWING_STEMS_PER_HA text(20), I1_SPECIES_CODE_5 text(20), BEC_SITE_TYPE text(20), I1_SPECIES_CODE_1 text(20), I4_SPECIES_PERCENT_3 text(20), I1_SPECIES_PERCENT_2 text(20), I1_SPECIES_CODE_2 text(20), I1_SPECIES_CODE_3 text(20), I3_SPECIES_PERCENT_1 text(20), SILV_NON_MAPPED_AREA text(20), I_TOTAL_STEMS_PER_HA text(20), I3_SPECIES_AGE_2 text(20), I2_SPECIES_PERCENT_5 text(20), I2_MORE_SPECIES_EXIST_IND text(20), I4_SPECIES_PERCENT_4 text(20), FEATURE_CLASS_SKEY text(20), I2_SPECIES_AGE_1 text(20), I1_BASAL_AREA text(20),
      I4_SPECIES_AGE_2 text(20), I3_TOTAL_WELL_SPACED_STEMS_HA text(20), I1_SPECIES_HEIGHT_2 text(20), SILV_POLYGON_NUMBER text(20), I1_SPECIES_HEIGHT_1 text(20), I2_INV_LABEL text(20), FEATURE_AREA text(20), I2_SPECIES_PERCENT_2 text(20), I4_CROWN_CLOSURE_PERCENT text(20), I4_SPECIES_PERCENT_1 text(20), BGC_ZONE_CODE text(20), I1_SPECIES_AGE_1 text(20), I1_CROWN_CLOSURE_PERCENT text(20), I4_BASAL_AREA text(20), I2_CROWN_CLOSURE_PERCENT text(20), I3_CROWN_CLOSURE_PERCENT text(20), BGC_SUBZONE_CODE text(20), I1_TOTAL_STEMS_PER_HA text(20), I_SPECIES_CODE_5 text(20), I4_TOTAL_WELL_SPACED_STEMS_HA text(20), SILV_POLYGON_NET_AREA text(20), I3_TOTAL_STEMS_PER_HA text(20), I4_SPECIES_HEIGHT_2 text(20), I2_TOTAL_STEMS_PER_HA text(20), I4_SPECIES_HEIGHT_1 text(20), I4_TOTAL_STEMS_PER_HA text(20), I2_FREE_GROWING_STEMS_PER_HA text(20), STOCKING_STATUS_CODE text(20), I1_WELL_SPACED_STEMS_PER_HA text(20), I1_TOTAL_WELL_SPACED_STEMS_HA text(20),
      I4_FREE_GROWING_STEMS_PER_HA text(20), I2_SPECIES_AGE_2 text(20), I3_SPECIES_PERCENT_5 text(20), I4_SPECIES_AGE_1 text(20), STOCKING_CLASS_CODE text(20), I_SPECIES_CODE_2 text(20), I_WELL_SPACED_STEMS_PER_HA text(20), REENTRY_YEAR text(20), OPENING_ID text(20), I3_MORE_SPECIES_EXIST_IND text(20), BEC_SITE_SERIES text(20), I_MORE_SPECIES_EXIST_IND text(20), I4_SPECIES_CODE_4 text(20), I3_INV_LABEL text(20), I4_SPECIES_CODE_5 text(20), STOCKING_STANDARD_UNIT_ID text(20), I1_SPECIES_PERCENT_3 text(20), I4_SPECIES_CODE_1 text(20), I4_SPECIES_CODE_2 text(20), FOREST_COVER_WHEN_UPDATED text(20), I3_SPECIES_PERCENT_2 text(20), I4_SPECIES_CODE_3 text(20), SILV_RESERVE_CODE text(20), BGC_PHASE text(20), BGC_VARIANT text(20), I2_TOTAL_WELL_SPACED_STEMS_HA text(20), I4_SPECIES_PERCENT_5 text(20), I1_SPECIES_PERCENT_4 text(20), BEC_SERAL text(20), I3_BASAL_AREA text(20),
      STOCKING_TYPE_CODE text(20), I_BASAL_AREA text(20), I3_SPECIES_CODE_4 text(20), STANDARDS_UNIT_ID text(20), SILV_POLYGON_AREA text(20), I3_SPECIES_CODE_5 text(20), I3_SPECIES_HEIGHT_2 text(20), I2_FOREST_COVER_LAYER_ID text(20), I2_SPECIES_PERCENT_3 text(20), I3_FOREST_COVER_LAYER_ID text(20), I3_SPECIES_CODE_1 text(20), I3_SPECIES_HEIGHT_1 text(20), I3_SPECIES_CODE_2 text(20), DATA_SOURCE_CODE text(20), I3_SPECIES_CODE_3 text(20), I4_SPECIES_PERCENT_2 text(20), I1_SPECIES_PERCENT_1 text(20), FOREST_COVER_WHO_CREATED text(20), I1_FOREST_COVER_LAYER_ID text(20), OBJECTID text(20), I4_FOREST_COVER_LAYER_ID text(20), FOREST_COVER_WHEN_CREATED text(20), I1_SPECIES_AGE_2 text(20), I2_SPECIES_PERCENT_4 text(20), I2_WELL_SPACED_STEMS_PER_HA text(20), I3_FREE_GROWING_STEMS_PER_HA text(20), I4_WELL_SPACED_STEMS_PER_HA text(20), GEOMETRY_AREA text(20), I_SPECIES_PERCENT_5 text(20), FEATURE_PERIMETER text(20),
      I_SPECIES_PERCENT_4 text(20), I_SPECIES_PERCENT_1 text(20), DATA_QUALITY_COMMENT text(20), I_SPECIES_PERCENT_3 text(20), I_SPECIES_PERCENT_2 text(20), TREE_COVER_PATTERN_CODE text(20), I4_INV_LABEL text(20)
